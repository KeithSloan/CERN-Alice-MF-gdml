#
#	Populate Volume directory
#
#	Creates STEP and OuterShell Brep
#
#	Select Volume/Part and invoke Macro
#
#	Copyright : Keith Sloan 			keith@sloan-home.co.uk
#


import time
import FreeCAD
import FreeCADGui as Gui
import Import
from PySide import QtGui

def getDirectory():
	print(f"Get Directory")
	dirPath = QtGui.QFileDialog().getExistingDirectory()
	if len(dirPath) > 0:
		print(f"Selected Path : {dirPath}")
		return  dirPath
 
def join(path, name):
	import os
	return(os.path.join(path, name))


doc = App.ActiveDocument
sel = Gui.Selection.getSelection()
print(f"Selection {sel}")
validSel = False
if len(sel) > 0:
	obj = sel[0]
	if obj.TypeId == "App::Part":
		print(f"Processing {obj.Label}")
		dirPath = getDirectory()
		#dirPath ="/tmp/test"
		if dirPath is not None:
			stepPath = join(dirPath, obj.Label+".step")
			print(f"Step Path {stepPath}")
			Import.export([obj], stepPath)
			#stepObj = Import.insert(stepPath, obj.Label+"_Step")
			workDoc = App.newDocument("Work")
			Import.insert(stepPath, workDoc.Name)
			stepObj = workDoc.getObject(obj.Label)			
			if hasattr(stepObj.Shape,"OuterShell"):
				exportPath = join(dirPath,obj.Label+"_OuterShell.brep")
				print(f"Exporting to {exportPath}")
				stepObj.Shape.OuterShell.exportBrep(exportPath)
			else:
				exportPath = join(dirPath, obj.Label+".brep")
				print(f"No OuterShell {obj.Label}")
				stepObj.Shape.exportBrep(exportPath)
			App.closeDocument("Work")
			validSel = True

if validSel == False:
     print('Select Part Volume')
